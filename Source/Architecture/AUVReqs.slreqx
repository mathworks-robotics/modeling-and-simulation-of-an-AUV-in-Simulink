# AUVReqs

## Underwater Vehicle Demo Requirements: References to Underwater Vehicle Demo Requirements.docx (Container)
Read-only references to Microsoft Word document.

### MissionSummary: Mission (Informational)
Mission
The mission for this vehicle is to search for a “black box” acoustic beacon on seafloor, navigate toward it, take a photo of the area to bring to surface, and report back with data on its estimated location
/
Figure 1: Whiteboard sketch of mission

### Functional_Requirements: Functional Requirements (Container)

#### Sensing_Requirements: Sensing (Container)

##### Sensing_EstimatePose: The system shall be capable of processing a combination of on-board sensors to estimate the pose of the underwater platform using either active or passive means (Functional)

##### Sensing_AcousticBeacon: The system shall have on-board sensors capable of passively detecting an acoustic beacon signal (Functional)

##### Sensing_ObstacleDetection: The system shall have onboard sensors capable of detecting obstacles in the underwater vehicle’s direct path (Functional)

##### Sensing_CommandSys: The system shall be capable of receiving commands from and communicating with an acoustic command system (Functional)

#### Perception_Requirements: Perception (Container)

##### Perception_UnderstandEnvironment: The platform shall create, in real-time, an understanding of the underwater environment, including… (Container)

###### Perception_Bathymetry: Bathymetry map of the sea floor (Functional)

###### Perception_Currents: An understanding of the ocean currents (Functional)

###### Perception_Obstacles: The existence and location of any solid obstacles in the direct path of the underwater vehicle (Functional)

##### Perception_LocateBeaconNED: If an underwater acoustic beacon is detected, the system shall be capable of estimating the position of the beacon relative to the underwater vehicle platform in local (e.g. North, East, Down) coordinates (Functional)

##### Perception_LocateBeaconECEF: If an underwater acoustic beacon is detected, the system shall be capable of estimating the position of the beacon in global (e.g., earth-centered, earth-fixed) coordinates via acoustic signal (Functional)

##### Perception_TrackBeacon: The platform shall be capable of tracking the estimated position of the acoustic beacon over time (Functional)

##### Perception_VisualizeBeacon: The system shall determine whether the beacon is visually apparent if imagery is available (Functional)

#### Planning_Requirements: Planning (Container)

##### Planning_InitialSearch: The system shall be capable of using its understanding of the underwater vehicle platform pose and the environment to create an initial search pattern that minimizes power consumption (Functional)

##### Planning_NavigatetoBeacon: When an underwater beacon is detected, the system shall be capable of path planning to navigate toward the beacon, avoiding any perceived obstacles, while minimizing power consumption (Functional)

##### Planning_NavigateandSurface: The system shall be able to determine whether there is enough power to return to the surface with at least 30% battery power remaining. (Functional)

##### Planning_AvoidObstacles: The underwater vehicle shall be capable of planning a navigation path around any obstacles that may be in the area of operation (Functional)

##### Planning_ReturntoHome: The system shall be capable of planning a return-to-home path to a predefined user-requested location that minimizes power consumption (Functional)

#### Action_Requirements: Action (Container)

##### Action_WaypointFollowing: The underwater vehicle shall autonomously navigate toward waypoints that are defined by the user or path planning algorithms (Functional)

##### Action_SearchModePattern: The underwater vehicle shall run a search mode pattern until the expected battery level upon return to a designated home point is above a predefined threshold (Functional)

##### Action_BeaconInterceptMission: If a beacon is detected and there is enough power available, the system shall alert the operator and run the Beacon Intercept mission (Functional)

##### Action_AcceptCommand: If a beacon is detected and there is not enough power available to intercept, the system shall alert the operator and wait 10 minutes for a command before executing return-to-home sequence. (Functional)

##### Action_BeaconInterceptEnd: The underwater vehicle shall run a Beacon Intercept mode until the expected battery level upon return to a designated home point is above a predefined threshold (Functional)

##### Action_ImageScene: Once within camera range, the vehicle shall capture images of the scene and save to on-board storage for visual confirmation upon surfacing (Functional)

##### Action_ReturntoHome: Once there is visual confirmation, the underwater vehicle shall alert the operator of the estimated location of the beacon and execute return-to-home sequence. (Functional)

#### MissionAbort_Requirements: Mission Abort (Container)

##### MissionAbort_PathDeviation: The system shall detect significant deviation from the planned path and if necessary, run return-to-home (RTH) or return-to-surface (RTS) mission abort sequence (Functional)

##### MissionAbort_HardwareFailure: When initiated by a hardware fault or failure, the system shall be able to run a return-to-home (RTH) or return-to-surface (RTS) abort sequence. Faults and failures and the sequence they initiate are defined in Table 1. (Functional)
When initiated by a hardware fault or failure, the system shall be able to run a return-to-home (RTH) or return-to-surface (RTS) abort sequence. Faults and failures and the sequence they initiate are defined in Table 1.
Table 1: Fault and Failure table and sequences to initiate
Fault/Failure Type
Fault/
Failure
Sequence to Initiate (return to surface or return to home)
Leak
Failure
RTS
10m deviation from path for 30 seconds
Fault
RTH
50m deviation from path for 30 seconds
Failure
RTS
Max Depth Threshold Exceeded
Failure
RTS
Internal temperature HIGH threshold exceeded
Fault
RTH
Internal temperature CRITICAL threshold exceeded
Failure
RTS
Low battery threshold exceeded
Fault
RTH
Critical battery threshold exceeded
Failure
RTS

##### MissionAbort_OperatorRequest: If requested by the operator, the system shall run a return-to-home (RTH) or return-to-surface (RTS) mission abort sequence (Functional)

##### MissionAbort_StatusComms: The system shall communicate health and status (estimated location, battery, mode) to the user at a predefined interval when executing a mission abort sequence (Functional)
